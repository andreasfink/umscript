UMDiscreteValue ::=  CHOICE {
    discreteNull        [0] NULL,
    discreteBool        [1] BOOL,
    discreteInt         [2] INTEGER,
    discreteLongLong    [3] INTEGER,
    discreteDouble      [4] UTF8STRING,
    discreteString      [5] UTF8STRING,
    discreteData        [6] OCTETSTRING,
    discreteArray       [7] OCTETSTRING,
    discreteStruct      [8] OCTETSTRING,
    discretePointer     [9] OCTETSTRING,
    discreteASN1Object  [10] OCTETSTRING,
}
